(progn
  (setq center (getpoint "\nChon diem tam cua mat: "))
  (setq radius (getdist center "\nNhap ban kinh mat: "))
  (command "_.circle" center radius)
  (setq eye_offset (* radius 0.4))
  (setq eye_radius (* radius 0.1))
  (setq left_eye (list (- (car center) eye_offset) (+ (cadr center) eye_offset)))
  (setq right_eye (list (+ (car center) eye_offset) (+ (cadr center) eye_offset)))
  (command "_.circle" left_eye eye_radius)
  (command "_.circle" right_eye eye_radius)
  (setq nose_center (list (car center) (- (cadr center) (* radius 0.2))))
  (setq nose_radius (* radius 0.15))
  (command "_.circle" nose_center nose_radius)
  (setq mouth_start (list (- (car center) (* radius 0.3)) (- (cadr center) (* radius 0.5))))
  (setq mouth_end (list (+ (car center) (* radius 0.3)) (- (cadr center) (* radius 0.5))))
  (setq mouth_mid (list (car center) (- (cadr center) (* radius 0.7))))
  (command "_.arc" mouth_start mouth_mid mouth_end)
  (princ)
)
